module network {

  namespace "http://example.com/network";
  prefix network;

  import ietf-inet-types {
    prefix inet;
  }
  import tailf-common {
    prefix tailf;
  }
  import tailf-ncs {
    prefix ncs;
  }

  description
    "Bla bla...";

  revision 2016-01-01 {
    description
      "Initial revision.";
  }

  typedef ipv4-prefix {
       type string {
         pattern
            '(([0-9]|[1-9][0-9]|1[0-9][0-9]|2[0-4][0-9]|25[0-5])\.){3}'
          +  '([0-9]|[1-9][0-9]|1[0-9][0-9]|2[0-4][0-9]|25[0-5])'
          + '/(([0-9])|([1-2][0-9])|(3[0-2]))';
       }
  }

  typedef solution-ID {
       type string {
         pattern
            '1\-'+'00[0-9]{8}';
       }
  }

  typedef route-target {
       type string {
         pattern
           '(0:(6553[0-5]|655[0-2][0-9]|65[0-4][0-9]{2}|'
         +     '6[0-4][0-9]{3}|'
         +     '[1-5][0-9]{4}|[1-9][0-9]{0,3}|0):(429496729[0-5]|'
         +     '42949672[0-8][0-9]|'
         +     '4294967[01][0-9]{2}|429496[0-6][0-9]{3}|'
         +     '42949[0-5][0-9]{4}|'
         +     '4294[0-8][0-9]{5}|429[0-3][0-9]{6}|'
         +     '42[0-8][0-9]{7}|4[01][0-9]{8}|'
         +     '[1-3][0-9]{9}|[1-9][0-9]{0,8}|0))|'
         + '(1:((([0-9]|[1-9][0-9]|1[0-9]{2}|2[0-4][0-9]|'
         +     '25[0-5])\.){3}([0-9]|[1-9][0-9]|'
         +     '1[0-9]{2}|2[0-4][0-9]|25[0-5])):(6553[0-5]|'
         +     '655[0-2][0-9]|'
         +     '65[0-4][0-9]{2}|6[0-4][0-9]{3}|'
         +     '[1-5][0-9]{4}|[1-9][0-9]{0,3}|0))|'
         + '(2:(429496729[0-5]|42949672[0-8][0-9]|'
         +     '4294967[01][0-9]{2}|'
         +     '429496[0-6][0-9]{3}|42949[0-5][0-9]{4}|'
         +     '4294[0-8][0-9]{5}|'
         +     '429[0-3][0-9]{6}|42[0-8][0-9]{7}|4[01][0-9]{8}|'
         +     '[1-3][0-9]{9}|[1-9][0-9]{0,8}|0):'
         +     '(6553[0-5]|655[0-2][0-9]|65[0-4][0-9]{2}|'
         +     '6[0-4][0-9]{3}|'
         +     '[1-5][0-9]{4}|[1-9][0-9]{0,3}|0))|'
         + '(6(:[a-fA-F0-9]{2}){6})|'
         + '(([3-57-9a-fA-F]|[1-9a-fA-F][0-9a-fA-F]{1,3}):'
         +     '[0-9a-fA-F]{1,12})';
        }

    }

    grouping classes {
        leaf STANDARD{

                type union{
                    type uint32{
                        range "1..100";
                    }
                    type enumeration{
                        enum n/a;
                    }
                }
                default n/a;
        }    
        leaf BUSINESS{

                type union{
                    type uint32{
                        range "1..100";
                    }
                    type enumeration{
                        enum n/a;
                    }
                }
                default n/a;

        }
        leaf VIDEO{

                type union{
                    type uint32{
                        range "1..100";
                    }
                    type enumeration{
                        enum n/a;
                    }
                }
                default n/a;


        }
        leaf VOICE{

                type union{
                    type uint32{
                        range "1..100";
                    }
                    type enumeration{
                        enum n/a;
                    }
                }
                default n/a;

        }
        leaf INTERACTIVE{

                type union{
                    type uint32{
                        range "1..100";
                    }
                    type enumeration{
                        enum n/a;
                    }
                }
                default n/a;

        }
    }


   container network {
    description "This is an RFS skeleton service";
    presence network;

    
    list cust {
        key vrf;
        leaf vrf {
            tailf:info "VRF :";
            tailf:cli-allow-range;
            type string;
        }

        leaf description {
            mandatory true;
            type string;
        }
 
    // vpn <----start---->
        list l3vpn {
            key 'vrf';
            leaf vrf {
                type enumeration {
                    enum vrf-defination;
                }
            } 
         
            leaf-list device {
                type leafref {
                    path "/ncs:devices/ncs:device/ncs:name";
                }
            }

            leaf rd {
                tailf:info "example : xx:xx";
                type route-target;
                mandatory true;
                
            }

            leaf-list rtExp {
                tailf:info "example : xx:xx";
                type route-target;
            }

            leaf-list rtImp {
                tailf:info "example : xx:xx";
                type route-target;

            }
            uses ncs:service-data;
            ncs:servicepoint network-servicepoint;
 
        }
    // l3vpn <----END---->


    // vpn <----start---->

        container vpn {

            list solutionID {
                key "solution_id";

                leaf solution_id {
                    tailf:info "example : 1-00xxxxxxxx";
                    type solution-ID;
                    }

                leaf description {
                    mandatory true;
                    type string;
                }
                
            // INTERFACE CONFIGURATION

                list interface {
                    key "interface_type interface_name";
                    leaf interface_type {
                        tailf:info "Ethernet";
                        type enumeration {
                            enum Ethernet;
                        }
                    }
                    leaf interface_name {
                        type string;
                    }

                    uses ncs:service-data;
                    ncs:servicepoint vpn-servicepoint;
                    
                    leaf device {
                        type leafref {
                            path 
                        "/network/cust[vrf=current()/../../../../vrf]/l3vpn/device";
                        }
                    }

                    leaf policy-map {
                         type leafref {
                            path "/network/cust[vrf=current()/../../../../vrf]/vpn/solutionID[solution_id=current()/../../solution_id]/qos/shaper_size";
                        }
                    }
                    leaf vlan {
                        config false;
                        tailf:cdb-oper {
                        tailf:persistent true;
                        }
                        type string;
        
                        }
                    leaf pe-interface {
                        config false;
                        tailf:cdb-oper {
                        tailf:persistent true;
                        }
                        type string;
        
                        }

                    leaf ip {
                        tailf:info "example : x.x.x.x";
                        type inet:ipv4-address;
                        }

                    leaf mask {
                        tailf:info "example : 255.255.255.0";
                        type inet:ipv4-address;

                    }

        
                    leaf status {
                        type enumeration {
                            enum up;
                            enum down;

                        }
                        default up;
                    }

                    leaf reason {
                        mandatory true;
                        when "../status = 'down'";
                        type enumeration{
                            enum suspension;
                            enum troubleshooting;
                        }
                    }

                    leaf SR {
                        tailf:info "SRxxxxxx-xxxxxx";
                        mandatory true;
                        when "../reason = 'suspension'";
                        type string;
                    }

                }
                //-------------------INTERFACE--EBD----    
                

                // BGP CONFIGURATION

                container bgp{ 
                    list neighbor {
                        key "neighbor_ip";
                        leaf neighbor_ip {
                            tailf:info "example : x.x.x.x";
                            type inet:ipv4-address;
                        }
                        
                        leaf remote_as {
                            tailf:info "range : 1-65535";
                            mandatory true;
                            type uint32{
                                range "1..65535";
                            }
                        }
                        leaf device {
                            type leafref{
                                path 
                                "/network/cust[vrf=current()/../../../../../vrf]/vpn/solutionID[solution_id=current()/../../../solution_id]/interface/device";
                            }

                        }

                        leaf rplIN {
                            tailf:info "inbound lp_1500 or lp_2000";
                            type enumeration {
                                    enum lp_1500;
                                    enum lp_2000;
                                }
                            default lp_2000;
                        }

                        leaf rplOUT {
                            type string;
                            default n/a;
                        }
                            
                        leaf soo {
                            tailf:info "example xx:xx";
                            type route-target;
                        }

                        leaf shutdown {
                            type enumeration {
                                enum true;
                                enum false;
                            }

                            default false;
                        }
                        uses ncs:service-data;
                        ncs:servicepoint bgp-servicepoint;

                                    
                    }
                    
                }        
        
                // STATIC

                container static {
                    list network {
    
                        key "prefix";
   
                        leaf next-hop{
                            tailf:info "example x.x.x.x";
                            type inet:ipv4-address;
                            mandatory true;
                        }
                        
                        leaf prefix {
                            tailf:info "example : x.x.x.x/x";
                            type ipv4-prefix;
                        }
                        
                        
                        
                        leaf Ethernet {
                            type leafref{
                                 path 
                            "/network/cust[vrf=current()/../../../../../vrf]/vpn/solutionID[solution_id=current()/../../../solution_id]/interface/interface_name";
                            }
                            mandatory true;
                        }


                           
                        leaf device {
                            type leafref{
                                path 
                                "/network/cust[vrf=current()/../../../../../vrf]/vpn/solutionID[solution_id=current()/../../../solution_id]/interface/device";
                            }

                        }                    
                        uses ncs:service-data;
                        ncs:servicepoint static-servicepoint;
                       
                    }

                }

                
                list qos {
                    key 'shaper_size';
                    leaf shaper_size {
                        type string;

                    }

                    uses classes; 

                    leaf policy_name {
                        config false;
                        tailf:cdb-oper {
                        tailf:persistent true;
                        }
                        type string;
        
                        }


                    leaf-list device {
                        
                        type leafref{
                        path 
                        "/network/cust[vrf=current()/../../../../vrf]/vpn/solutionID[solution_id=current()/../../solution_id]/interface/device";
                        }

                    }
                     uses ncs:service-data;
                    ncs:servicepoint qos-vpn-servicepoint;

                   
                }   

            }
            
        
            // end ----OF----STATIC


            list global-vpn-bgp {
                key "device";
                leaf default-information-originate {
                    type enumeration {
                        enum true;
                        enum false;
                    }
                        default false;
                }
                leaf device {
                    type leafref {
                        path 
                    "/network/cust[vrf=current()/../../../vrf]/l3vpn/device";
                    }
                }
                       
                uses ncs:service-data;
                ncs:servicepoint global-vpn-bgp-servicepoint;

                    
            }
        }
            // end ----OF----global-vpn-bgp
           
                 //dia start 
        container dia {

            // dia--interface--start
            list SolutionID {
                
                key "id_name";
                leaf id_name {
                    type string;
                }

                leaf description {
                    type string;
                }

                list interface {
                    key "interface_type interface_name";
                    leaf interface_type {
                        tailf:info "Ethernet";
                        type enumeration {
                            enum Ethernet;
                        }
                    }
                    leaf interface_name {
                        type string;
                    }

                    uses ncs:service-data;
                    ncs:servicepoint dia-interface-servicepoint;

                    leaf device {
                        type leafref {
                        path "/ncs:devices/ncs:device/ncs:name";
                        }
                    }
                    leaf vlan {
                        config false;
                        tailf:cdb-oper {
                        tailf:persistent true;
                        }
                        type string;
        
                        }
                    leaf pe-interface {
                        config false;
                        tailf:cdb-oper {
                        tailf:persistent true;
                        }
                        type string;
        
                        }
                    leaf ip {
                        tailf:info "example : x.x.x.x";
                        type inet:ipv4-address;
                        
                    }

                    leaf mask {
                        tailf:info "example : 255.255.255.0";
                        type inet:ipv4-address;

                    }

                    leaf description {
                        type string;
                    }
        
                    leaf shutdown {
                        type enumeration {
                            enum true;
                            enum false;

                        }
                        default false;
                    }

                }

                // dia---interface--end
                // dia ---Static--start 
                container static {
                    list network {

                        key "prefix";

                        leaf next-hop{
                            tailf:info "example x.x.x.x";
                            type inet:ipv4-address;
                            mandatory true;
                        }
                        
                        leaf prefix {
                            tailf:info "example : x.x.x.x/x";
                            type ipv4-prefix;
                        }

                        container interface {
                            leaf Ethernet {
                                tailf:info "Ethernet";
                                type string;
                                mandatory true;
                            }

                        }
                        uses ncs:service-data;
                        ncs:servicepoint dia-static-servicepoint;
                        
                        leaf device {
                            type leafref {
                            path "/ncs:devices/ncs:device/ncs:name";
                            }

                        }
          
                    }

                }
            // dia---static--end

                container bgp{ 
                    list neighbor {
                        key "neighbor_ip";
                        leaf neighbor_ip {
                            tailf:info "example : x.x.x.x";
                            type inet:ipv4-address;
                        }
                        uses ncs:service-data;
                        ncs:servicepoint dia-bgp-servicepoint;

                        leaf remote_as {
                            tailf:info "range : 1-65535";
                            type uint32{
                                range "1..65535";
                            }
                            mandatory true;
                        }

                        leaf device {
                            type leafref {
                            path "/ncs:devices/ncs:device/ncs:name";
                            }
                        }

                        leaf rplIN {
                            tailf:info "insert inbound policy";
                            type string;

                            default deny_all_in;
                        }

                        leaf rplOUT {
                            tailf:info "outbound route-policy";
                            type string;

                            default default_only;                                
                        }
                            
                    }
                        
                    
                }

            }

        }

                // dia end
    
    }
    
  }
// vpn <----END---->
}
